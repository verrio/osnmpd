--
-- message format for IPC channels of the SNMP agent:
-- trap request messages, control request messages,
-- control response messages
--

SNMPAgentCommunication DEFINITIONS AUTOMATIC TAGS ::=
BEGIN
EXPORTS ALL;

AgentFlags ::= BIT STRING (SIZE (8))

-- trap request dispatched to the agent's message queue
--
-- some pairs of trapcodes are mapped to RFC-defined OIDs:
-- (0x6300,0x0407) : SNMP authentication failure
-- (0x0002,0x0000) : cold start
-- (0x0000,0x0107) : link up
-- (0x0000,0x0108) : link down
-- (0x0020,0x0000) : battery voltage low
-- (0x001f,0x0000) : replace battery
-- (0x0000,0x0086) : battery charge start
-- (0x0000,0x0087) : battery charge stop
--
AgentTrapRequest ::= SEQUENCE {
    version INTEGER (0..255) DEFAULT 0, -- reserved for future usage
    flags AgentFlags DEFAULT '00'H, -- reserved for future usage
    timeStamp INTEGER (0..18446744073709551615), -- milliseconds since epoch
    trapCode1 INTEGER (0..65535) DEFAULT 0,  -- trap code 1
    trapCode2 INTEGER (0..65535) DEFAULT 0, -- trap code 2
    arguments SEQUENCE OF VarArguments -- optional arguments included in event (max 8)
}

-- control socket request
--
-- available commands:
-- 0x00: get daemon name
-- 0x01: get version
-- 0x02: get uptime
-- 0x03: get enabled interfaces
-- 0x04: set enabled interfaces (arg contains sequence of iface names)
-- 0x05: get port
-- 0x06: set port (arg contains port)
-- 0x07: get notification config
-- 0x08: set notification config (arg contains enabled state,
--       confirmation state, user slot, destination,
--       port and retry count/timeout)
-- 0x09: get user config (arg contains user slot)
-- 0x0A: set user config (arg contains user slot, enabled state,
--       user name, security model, security level)
-- 0x0B: set user auth password (arg contains user slot, password)
-- 0x0C: set user priv password (arg contains user slot, password)
-- 0x0D: get engine id
-- 0x0E: set engine id (arg contains octet-string with engine id)
--
AgentCtlRequest ::= SEQUENCE {
    version INTEGER (0..255) DEFAULT 0, -- reserved for future usage
    flags AgentFlags, -- reserved for future usage
    requestId INTEGER (0..255), -- tracking ID
    requestType ENUMERATED, -- enum with request command
    arguments SEQUENCE OF VarArguments -- request arguments
}

-- control socket response
AgentCtlResponse ::= SEQUENCE {
    version INTEGER (0..255) DEFAULT 0, -- reserved for future usage
    flags AgentFlags, -- reserved for future usage
    responseId INTEGER (0..255), -- echo'ed tracking ID
    resultCode ResultCode, -- result of command execution
    arguments SEQUENCE OF VarArguments -- response arguments
}

ResultCode ::= ENUMERATED {
    success(0), -- request processed correctly
    otherReason(1), -- failure which is not covered by any of the error codes below
    parseError(2), -- given request could not be parsed
    commandNotAvailable(3), -- the requested command is not available on this agent
    argumentsMissing(4), -- request is missing one or more arguments
    argumentsWrongLength(5), -- request has argument(s) of invalid length
    argumentsWrongType(6), -- request has argument(s) of invalid type
    argumentsInvalid(7), -- request has argument(s) which are invalid (context-specific)
    dataConstraintViolation(8), -- executing the request would break
                                -- one or more data constraints
    notEnoughMemory(9), -- insufficient RAM available to handle this request
    missingFile(10), -- one or more files on disk are missing which prevents
                     -- the correct handling of this request
    diskNotAvailable(11), -- disk (or database) is not available.
    diskFull(12), -- disk (or database) is full.
    diskCorrupt(13), -- disk (or database) is corrupt.
    networkUnavailable(14), -- network access is not available.
    requestCancelled(15), -- request was canceled while processing was ongoing.
    previousRequestStillOngoing(16), -- previous request is still ongoing
                                     -- (in case handling is done asynchronously)
    missingSecret(17), -- request required security key(pair)
                       -- or password which is not available
    securityError(18), -- request execution met security related
                       -- error (e.g. decryption failure)
    temporarilyUnavailable(19), -- request could not be executed because
                                -- one or more resources/constraints are
				-- not validated right now
    hardwareFault(20), -- unexpected hardware behavior was met while
                       -- trying to execute the request
    osFault(21), -- unexpected OS behavior was met while
                 -- trying to execute the request
    requestTimeout(22), -- agent process timed out while waiting
                        -- on response from external process
    notImplemented(23) -- request is applicable to this agent,
                       -- but nevertheless not implemented
}

-- possible arguments included in a ctl message.
VarArguments ::= CHOICE {
    null NULL,
    boolean BOOLEAN,
    integer INTEGER,
    float REAL,
    octetString OCTET STRING,
    sequence SEQUENCE OF VarArguments
}

END
